standard library package Objects {
    class Object :> Occurrences::Occurrence {
        // enactedPerformance: Performance [0 .. *]; 
        // involvedIn: Performance [0 .. *];
        //;  
    }
    feature objects: Object [0 .. *]; 
}
